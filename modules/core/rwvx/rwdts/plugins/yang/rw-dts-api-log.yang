/* STANDARD-RIFT-IO-COPYRIGHT */
/**
 * @file   rw-dts-api-log.yang
 * @author Rajesh Velandy
 * @date   2014/12/22
 * @brief  Riftware yang data schema for DTS API logging
 */

module rw-dts-api-log
{
  namespace "http://riftio.com/ns/riftware-1.0/rwdtsapilog";
  prefix "rwdtsapilog";


  import rw-base {
    prefix rwbase;
    }


  import rw-pb-ext {
    prefix "rwpb";
  }

  import rw-yang-types {
    prefix "rwt";
  }

  import rw-notify-ext {
    prefix "rwnotify";
  }

  import rw-log {
    prefix "rwlog";
  }

  description "RW.DTS API logging definitions";

  revision 2014-12-22 {
    description "Initial revision";
    reference "Rift Yang Data schema for DTS API Logging";
  }



  notification dtsapi-debug {
    rwnotify:log-event-id 00030000;
    description "DTS API generic debug log";
    uses rwlog:severity-debug;
    leaf log {
      type string;
    }
  }

  notification dtsapi-info {
    rwnotify:log-event-id 00030001;
    description "DTS API generic info log";
    uses rwlog:severity-info;
    leaf log {
      type string;
    }
  }

  notification dtsapi-notice {
    rwnotify:log-event-id 00030002;
    description "DTS API generic notice log";
    uses rwlog:severity-notice;
    leaf log {
      type string;
    }
  }

  notification dtsapi-warning {
    rwnotify:log-event-id 00030003;
    description "DTS API generic warning log";
    uses rwlog:severity-warning;
    leaf log {
      type string;
    }
  }

  notification dtsapi-error {
    rwnotify:log-event-id 00030004;
    description "DTS API generic error log";
    uses rwlog:severity-error;
    leaf log {
      type string;
    }
  }

  notification dtsapi-critical {
    rwnotify:log-event-id 00030005;
    description "DTS API generic critical log";
    uses rwlog:severity-critical;
    leaf log {
      type string;
    }
  }

  notification dtsapi-alert {
    rwnotify:log-event-id 00030006;
    description "DTS API generic alert log";
    uses rwlog:severity-alert;
    leaf log {
      type string;
    }
  }

  notification dtsapi-emergency {
    rwnotify:log-event-id 00030007;
    description "DTS API generic emergency log";
    uses rwlog:severity-emergency;
    leaf log {
      type string;
    }
  }

  /*
   * Grouping for DTS  generic API related logs
   */

  grouping dts-api-attr {
    description "DTS API init related grouping";
    leaf member {
      description "DTS member";
      type string;
    }
    leaf router {
      description "DTS router";
      type string;
    }
  }

  /*
   * Info log when DTS API is inited
   */
  notification dtsapi-inited {
    rwnotify:log-event-id 00030008;
    description "DTS API inited";
    uses rwlog:severity-info;
    uses dts-api-attr;
    leaf log {
      description "Log string";
      type string;
    }
  }

  /*
   * DTS API  failed to initialize
   */
  notification dtsapi-init-failed {
    rwnotify:log-event-id 00030009;
    description "DTS API initilization failed";
    uses rwlog:severity-critical;
    uses dts-api-attr;
    leaf log {
      description "Log string";
      type string;
    }
  }

  /*
   * DTS API deinit invoked with NULL handle
   */
  notification dtsapi-deinit-null-apih {
    rwnotify:log-event-id 00030011;
    description "DTS API deinit invoked with NULL API handle";
    uses rwlog:severity-warning;
    leaf log {
      description "Log string";
      type string;
    }
  }

  /*
   * Info log when DTS API is deinited
   */
  notification dtsapi-deinited {
    rwnotify:log-event-id 00030013;
    description "DTS API deinited";
    uses rwlog:severity-info;
    uses dts-api-attr;
    leaf log {
      description "Log string";
      type string;
    }
  }

  /*
   * DTS transaction related attributes
   */

  grouping dts-xact-attr {
    description "DTS transaction related attibutes";
    leaf xact-id {
      description "DTS Transaction related identifier";
      type string;
    }
  }

  /*
   * Info log when DTS xact is inited
   */
  notification xact-inited {
    rwnotify:log-event-id 00030014;
    description "DTS API inited";
    uses rwlog:severity-debug;
    uses dts-xact-attr;
    leaf log {
      description "Log string";
      type string;
    }
  }

  /*
   * Info log when DTS xact is deinited
   */
  notification xact-deinited {
    rwnotify:log-event-id 00030015;
    description "DTS API de-inited";
    uses rwlog:severity-debug;
    uses dts-xact-attr;
    leaf log {
      description "Log string";
      type string;
    }
  }

  /*
   * Received async response status from router
   */
  notification rsp-status-rcvd {
    rwnotify:log-event-id 00030016;
    description "Response status received";
    uses rwlog:severity-debug;
    uses dts-xact-attr;
    leaf log {
      description "Log string";
      type string;
    }
  }

  /*
   * Member received duplicate query
   */
  notification duplicate-query-rcvd {
    rwnotify:log-event-id 00030017;
    description "Member received duplicate query";
    uses rwlog:severity-warning;

    uses dts-xact-attr;

    leaf log {
      description "Log string";
      type string;
    }
    leaf query-id {
      description "Query Id";
      type uint32;
    }
    leaf keyspec {
      description "keyspec in received query";
      type string;
    }
  }

  /*
   * DTS started timer 
   */
  notification timer-started {
    rwnotify:log-event-id 00030018;
    description "DTS API timer started";
    uses rwlog:severity-debug;
    uses dts-api-attr;
    leaf log {
      type string;
    }
  }

  /*
   * DTS successully updated redis
   */
  notification dtsapi-updated-redis {
    rwnotify:log-event-id 00030019;
    description "DTS successfully updated redis";
    uses rwlog:severity-debug;
    leaf log {
      type string;
    }
  }

  /*
   * DTS registration related common attributes
   */

  grouping dts-reg-attr {
    description "DTS registration related attributes";
    uses dts-api-attr;
    leaf keyspec {
      description "keyspec associated with this registration";
      type string;
    }
  }
  /*
   * DTS Reg retry 
   */
  notification reg-retry{
    rwnotify:log-event-id 00030020;
    description "DTS registration retry";
    uses rwlog:severity-info;

    uses dts-api-attr;

    leaf log {
      description "log message";
      type string;
    }

    leaf retry-count {
      type uint32;
    }
  }

  /*
   * DTS Reg retry exceeded
   */
  notification reg-retry-exceeded {
    rwnotify:log-event-id 00030021;
    description "DTS registration retry exceeded";
    uses rwlog:severity-critical;

    uses dts-api-attr;

    leaf log {
      description "log message";
      type string;
    }

    leaf retry-count {
      description "No of retries with router";
      type uint32;
    }
  }

  /*
   * DTS registred
   */
  notification registered {
    rwnotify:log-event-id 00030022;
    description "DTS member successfully registered with router";
    uses rwlog:severity-info;

    uses dts-api-attr;

    leaf log {
      description "log message";
      type string;
    }

    leaf retry-count {
      description "No of retries with router";
      type uint32;
    }
  }

  /*
   * DTS API register with router
   */
  notification register-router {
    rwnotify:log-event-id 00030023;
    description "DTS API register with router";
    uses rwlog:severity-debug;

    uses dts-api-attr;

    leaf log {
      description "Log string";
      type string;
    }
  }

  /*
   * DTS registration added/updated
   */
  notification reg-added {
    rwnotify:log-event-id 00030023;
    description "DTS registration added/updated";
    uses rwlog:severity-debug;
    uses dts-reg-attr;

    leaf log {
      description "log message";
      type string;
    }

    leaf audit-state {
      description "Audit state";
      type uint32;
    }
  }

  /*
   * DTS dispatch response to an outstanding Query
   */
  notification query-rsp-dispatch {
    rwnotify:log-event-id 00030024;
    description "Dispacth response to an outstanding query";
    uses rwlog:severity-debug;

    uses dts-xact-attr;

    leaf log {
      description "log message";
      type string;
    }
   leaf query-id {
     description "Query Id";
     type uint32;
   }
   leaf corr-id {
     description "Correlation Id";
     type uint64;
   }
   leaf query-evtrsp {
     description "Query event response";
     type string;
   }
  }

  /*
   * DTS failed to dispatch response to an outstanding Query
   */
  notification query-rsp-dispatch-failed {
    rwnotify:log-event-id 00030025;
    description "Failed to dispacth response to an outstanding query";
    uses rwlog:severity-critical;
    uses dts-xact-attr;
    leaf log {
      description "log message";
      type string;
    }
    leaf query-id {
      description "Query Id";
      type uint32;
    }
    leaf corr-id {
      description "Correlation Id";
      type uint64;
    }
    leaf query-evtrsp {
      description "Query event resposne";
      type string;
    }
  }

  /*
   * DTS member responding to xact
   */
  notification member-xact-rsp {
    rwnotify:log-event-id 00030026;
    description "DTS member responding to transaction";
    uses rwlog:severity-info;
    uses dts-xact-attr;

    leaf log {
      description "log message";
      type string;
    }
    leaf query-evtrsp {
      description "Query event resposne";
      type string;
    }
  }

  /*
   * Send shard info to router
   */
  notification send-shard-info {
      rwnotify:log-event-id 00030027;
    description "Send shard info to router";
    uses rwlog:severity-debug;
    uses dts-api-attr;
    leaf log {
      description "Log string";
      type string;
    }
  }

  /*
  /*
   * Send shard info to router
   */
  notification data-member-api-cb {
      rwnotify:log-event-id 00030028;
    description "Data member API triggered callback";
    uses rwlog:severity-debug;
    uses dts-xact-attr;
    leaf log {
      description "Log string";
      type string;
    }
    leaf status {
      description "Return status";
      type uint32;
    }
    leaf callback {
      description "Callback fn";
      type string;
    }
  }

  /*
  /*
   * Data member API error
   */
  notification data-member-api-error {
      rwnotify:log-event-id 00030029;
    description "Data member API error";
    uses rwlog:severity-warning;
    uses dts-api-attr;
    leaf log {
      description "Log string";
      type string;
    }
  }

  /*
   * DTS API register successfully with router
   */
  notification register-success {
      rwnotify:log-event-id 00030030;
    description "DTS API register successfully with router";
    uses rwlog:severity-info;

    uses dts-api-attr;

    leaf log {
      description "Log string";
      type string;
    }
    leaf retran-count {
      description "Number of retransmissions";
      type uint32;
    }
  }

  /*
   * DTS API register  failed  with router
   */
  notification register-failed {
      rwnotify:log-event-id 00030031;
    description "DTS API registeration failed with router";
    uses rwlog:severity-error;

    uses dts-api-attr;

    leaf log {
      description "Log string";
      type string;
    }
    leaf retran-count {
      description "Number of retransmissions";
      type uint32;
    }
  }

  /*
  /*
   * registration callback
   */
  notification register-cb {
      rwnotify:log-event-id 00030032;
    description "registration callback received";
    uses rwlog:severity-debug;
    uses dts-xact-attr;
    leaf log {
      description "Log string";
      type string;
    }
  }

  /*
  /*
   * keyspec updated with Pathentry
   */
  notification keyspec-updated-pe {
      rwnotify:log-event-id 00030033;
    description "keyspec updated with pe";
    uses rwlog:severity-debug;

    uses dts-api-attr;

    leaf log {
      description "Log string";
      type string;
    }
    leaf path-entry {
      description "path entry";
      type string;
    }
  }
  
  /*
   * Member reeived prepare
   */
  notification prepare-rcvd {
      rwnotify:log-event-id 00030034;
    description "Member received prepare";
    uses rwlog:severity-debug;

    uses dts-xact-attr;

    leaf log {
      description "Log string";
      type string;
    }
    leaf num-blocks {
      description "Number of blocks in transaction";
      type uint64;
    }
  }

  /*
   * Member reeived query
   */
  notification query-rcvd {
      rwnotify:log-event-id 00030035;
    description "Member received query";
    uses rwlog:severity-debug;

    uses dts-xact-attr;

    leaf log {
      description "Log string";
      type string;
    }
    leaf query-id {
      description "Query Id";
      type uint32;
    }
    leaf keyspec {
      description "keyspec in received query";
      type string;
    }
  }

  /*
   * Member received pre-commit
   */
  notification precommit-rcvd {
      rwnotify:log-event-id 00030036;
    description "Member received pre-commit";
    uses rwlog:severity-debug;

    uses dts-xact-attr;

    leaf log {
      description "Log string";
      type string;
    }
  }


  /*
   * Member received abort
   */
  notification abort-rcvd {
      rwnotify:log-event-id 00030037;
    description "Member received abort";
    uses rwlog:severity-debug;

    uses dts-xact-attr;

    leaf log {
      description "Log string";
      type string;
    }
  }

  /*
   * Member received commit
   */
  notification commit-rcvd {
      rwnotify:log-event-id 00030038;
    description "Member received commit";
    uses rwlog:severity-debug;

    uses dts-xact-attr;

    leaf log {
      description "Log string";
      type string;
    }
  }

  /*
   * Member transaction not found
   */
  notification xact-not-found {
      rwnotify:log-event-id 00030039;
    description "Member tranaction not found";
    uses rwlog:severity-debug;

    uses dts-xact-attr;

    leaf log {
      description "Log string";
      type string;
    }
  }

  /*
   * Commit record added
   */
  notification commit-rec-added {
      rwnotify:log-event-id 00030040;
    description "Commit record added";
    uses rwlog:severity-debug;

    uses dts-xact-attr;

    leaf log {
      description "Log string";
      type string;
    }

    leaf query-action  {
      description "Query action";
      type string ;
    }

    leaf keyspec {
      description "Query keyspec";
      type string ;
    }
  }

  /*
   * xact fsm failed
   */
  notification xact-fsm-failed {
      rwnotify:log-event-id 00030041;
    description "xact fsm failed";
    uses rwlog:severity-warning;

    uses dts-xact-attr;

    leaf log {
      description "Log string";
      type string;
    }

    leaf xact-state  {
      description "Member transaction state";
      type string ;
    }

    leaf xact-event {
      description "Member transaction event";
      type string ;
    }

    leaf member-name {
      description "Member info";
      type string;
    }
  }

  /*
   * Pending Query responses
   */
  notification query-pending-rsp {
      rwnotify:log-event-id 00030042;
    description "Query pending responses";
    uses rwlog:severity-info;

    uses dts-xact-attr;

    leaf log {
      description "Log string";
      type string;
    }

    leaf num-prepares-dispatched {
      description "Number of prepares dispacthed";
      type uint32 ;
    }

    leaf num-rsp-rcvd {
      description "Number of query responses received";
      type uint32 ;
    }
  }

  /*
   * Member xact fsm transition
   */
  notification xact-fsm-transition {
      rwnotify:log-event-id 00030043;
    description "Member xact fsm transition";
    uses rwlog:severity-debug;

    uses dts-xact-attr;

    leaf log {
      description "Log string";
      type string;
    }

    leaf xact-state  {
      description "Member transaction state";
      type string ;
    }

    leaf xact-event {
      description "Member transaction event";
      type string ;
    }
  }

  /*
   *  DTS Query bounced
   */
  notification query_bounced {
      rwnotify:log-event-id 00030044;
    description "DTS Query Bounced";
    uses rwlog:severity-info;

    uses dts-xact-attr;

    leaf log {
      description "Log string";
      type string;
    }

    leaf bounce-code {
      description "Bounce code";
      type int32;
    }
  }

  /*
   *  begining DTS transaction
   */
  notification begin-xact {
      rwnotify:log-event-id 00030045;
    description "Begining DTS transaction";
    uses rwlog:severity-debug;

    uses dts-xact-attr;

    leaf log {
      description "Log string";
      type string;
    }

    leaf num-blocks {
      description "Number of xact blocks";
      type uint32;
    }
  }

  /*
   * query in begin xact
   */
  notification begin-xact-query {
      rwnotify:log-event-id 00030046;
    description "Begining DTS transaction";
    uses rwlog:severity-debug;

    uses dts-xact-attr;

    leaf log {
      description "Log string";
      type string;
    }

    leaf queryidx {
      description "Query id";
      type uint32;
    }
    leaf keyspec {
      description "keyspec in query";
      type string;
    }
  }

  /*
   * prepare callback invoked
   */
  notification prepare-cb-invoked {
      rwnotify:log-event-id 00030047;
    description "prepare callback invoked";
    uses rwlog:severity-debug;

    uses dts-xact-attr;

    leaf log {
      description "Log string";
      type string;
    }
    leaf callback {
      description "Callback fn";
      type string;
    }
    leaf keyspec {
      description "keyspec in query";
      type string;
    }
  }

  /*
   * commit callback invoked
   */
  notification commit-cb-invoked {
      rwnotify:log-event-id 00030047;
    description "commit callback invoked";
    uses rwlog:severity-debug;

    uses dts-xact-attr;

    leaf log {
      description "Log string";
      type string;
    }
    leaf callback {
      description "Callback fn";
      type string;
    }
  }

  /*
   * pre-commit callback invoked
   */
  notification precommit-cb-invoked {
      rwnotify:log-event-id 00030048;
    description "precommit callback invoked";
    uses rwlog:severity-debug;

    uses dts-xact-attr;

    leaf log {
      description "Log string";
      type string;
    }
    leaf callback {
      description "Callback fn";
      type string;
    }
  }

  /*
   * abort callback invoked
   */
  notification abort-cb-invoked {
      rwnotify:log-event-id 00030048;
    description "abort callback invoked";
    uses rwlog:severity-debug;

    uses dts-xact-attr;

    leaf log {
      description "Log string";
      type string;
    }
    leaf callback {
      description "Callback fn";
      type string;
    }
  }

  /*
   * Async response destroyiong pending xact
   */
  notification async-rsp-destroy-pending-xact {
      rwnotify:log-event-id 00030049;
    description "Freeing pending destroy xact on query rsp(async)";
    uses rwlog:severity-info;

    uses dts-xact-attr;

    leaf log {
      description "Log string";
      type string;
    }

    leaf async_qrsp_sent {
      description "Number of async query responses sent";
      type uint32;
    }

    leaf async_qrsp_rsp_rcvd {
      description "Number of respnses rcvd for async query responses";
      type uint32;
    }
  }

  /*
   * Destroying a pendig xact
   */
  notification xact-pending-delete {
      rwnotify:log-event-id 00030050;
    description "xact pending delete";
    uses rwlog:severity-debug;

    uses dts-xact-attr;

    leaf log {
      description "Log string";
      type string;
    }

    leaf async_qrsp_sent {
      description "Number of async query responses sent";
      type uint32;
    }

    leaf async_qrsp_rsp_rcvd {
      description "Number of respnses rcvd for async query responses";
      type uint32;
    }
  }

  /*
   * Destroying a xact
   */
  notification xact-destroyed {
      rwnotify:log-event-id 00030051;
    description "Destroying a xact";
    uses rwlog:severity-debug;

    uses dts-xact-attr;

    leaf log {
      description "Log string";
      type string;
    }
  }

  /*
   * DTS Append member response to the query
   */
  notification query-append-rsp {
      rwnotify:log-event-id 00030052;
    description "Failed to dispacth response to an outstanding query";
    uses rwlog:severity-debug;

    uses dts-xact-attr;

    leaf log {
      description "log message";
      type string;
    }
    leaf query-id {
      description "Query Id";
      type uint32;
    }
    leaf corr-id {
      description "Correlation Id";
      type uint64;
    }
    leaf query-evtrsp {
      description "Query event resposne";
      type string;
    }
  }

  /*
   * DTS send query rsp async
   */
  notification query-rsp-async {
      rwnotify:log-event-id 00030052;
    description "DTS send query response asynchronously";
    uses rwlog:severity-debug;

    uses dts-xact-attr;

    leaf log {
      description "log message";
      type string;
    }
    leaf query-id {
      description "Query Id";
      type uint32;
    }
    leaf corr-id {
      description "Correlation Id";
      type uint64;
    }
    leaf query-evtrsp {
      description "Query event resposne";
      type string;
    }
  }

  /*
   * populate registration cache
   */
  notification populate-reg-cache {
    rwnotify:log-event-id 00030053;
    description "populate registration cache";
    uses rwlog:severity-notice;
    uses dts-reg-attr;

    leaf log {
      description "log message";
      type string;
    }
  }

  /*
   * populate registration cache callback
   */
  notification populate-reg-cache-rsp {
    rwnotify:log-event-id 00030054;
    description "populate registration cache";
    uses rwlog:severity-notice;
    uses dts-reg-attr;

    leaf log {
      description "log message";
      type string;
    }

    leaf num-result {
      description "Number of results";
      type uint32;
    }
  }

  /*
   * DTS API state change
   */
  notification dtsapi-state-changed {
    rwnotify:log-event-id 00030055;
    description "DTS API state changed";
    uses rwlog:severity-info;
    uses dts-api-attr;
    leaf log {
      description "Log string";
      type string;
    }
  }

  /*
   * DTS API set trace
   */
  notification trace-set {
    rwnotify:log-event-id 00030056;
    description "DTS API trace configured/set event";
    uses rwlog:severity-critical;
    uses dts-api-attr;
    leaf xpath {
      description "xpath targeted for tracing";
      type string;
    }
  }

  /*
   * DTS API trace events
   */

  notification trace-unknown {
    rwnotify:log-event-id 00030057;
    description "DTS API trace unknown type";
    uses rwlog:severity-critical;
    leaf xact-id        { type string; }
    leaf log            { type string; }
  }


  notification trace-req {
    rwnotify:log-event-id 00030058;
    description "DTS API trace REQ type";
    uses rwlog:severity-critical;
    leaf xact-id      { type string; }
    leaf event        { type string; }
    leaf srcpath      { type string; }
    leaf dstpath      { type string; }
    leaf state        { type string; }
    leaf resultcode   { type string; }
    leaf resultcount  { type int32;  }
    leaf ellapsedmsec { type uint64; }
    leaf queryidlist  { type string; }
  }

  notification trace-member-match {
    rwnotify:log-event-id 00030059;
    description "DTS API trace member match";
    uses rwlog:severity-critical;
    leaf xact-id          { type string; }
    leaf destination_path { type string; }
    leaf query            { type uint32; }
    leaf source_path      { type string; }
    leaf match_path       { type string; }
    leaf registration_id  { type uint32; }
  }

  notification trace-add-block {
    rwnotify:log-event-id 00030060;
    description "DTS API trace add block";
    uses rwlog:severity-critical;
    leaf xact-id          { type string; }
    leaf blockidx         { type uint32; }
    leaf destpath         { type string; }
    leaf log              { type string; }
  }

  notification trace-abort {
    rwnotify:log-event-id 00030061;
    description "DTS API trace abort ";
    uses rwlog:severity-critical;
    leaf xact-id          { type string; }
    leaf srcpath          { type string; }
    leaf dstpath          { type string; }
    leaf event            { type string; }
  }

  notification trace-route {
    rwnotify:log-event-id 00030062;
    description "DTS API trace route ";
    uses rwlog:severity-critical;
    leaf xact-id          { type string; }
    leaf queryid          { type uint64; }
    leaf matchpath        { type string; }
    leaf matchdesc        { type string; }
    leaf destpath         { type string; }
  }

  /*
   * DTS  audit failure
   */
  notification audit_failure {
    rwnotify:log-event-id 00030063;
    description "DTS audit failure";
    uses rwlog:severity-alert;
    uses dts-reg-attr;

    leaf log {
      description "log message";
      type string;
    }
  }

  /*
   * DTS  audit failure
   */
  notification begin-audit {
    rwnotify:log-event-id 00030064;
    description "DTS audit begin";
    uses rwlog:severity-debug;
    uses dts-reg-attr;

    leaf log {
      description "log message";
      type string;
    }
    leaf reg-id {
      description "registration id";
      type uint32;
    }
  }
  /*
   * populate registration cache callback
   */
  notification audit-rsp {
    rwnotify:log-event-id 00030065;
    description "DTS audit response";
    uses rwlog:severity-notice;
    uses dts-reg-attr;

    leaf log {
      description "log message";
      type string;
    }

    leaf num-result {
      description "Number of results";
      type uint32;
    }
  }

  /*
   * registration ready callback
   */
  notification reg-ready-cb-called {
    rwnotify:log-event-id 00030066;
    description "registration ready callback";
    uses rwlog:severity-debug;
    uses dts-reg-attr;

    leaf log {
      description "log message";
      type string;
    }

    leaf callback {
      description "Callback Fn";
      type string;
    }
  }

  /*
   * client callback
   */
  notification client-callback-triggered {
    rwnotify:log-event-id 00030067;
    description "client callback";
    uses rwlog:severity-debug;
    uses dts-xact-attr;

    leaf log {
      description "log message";
      type string;
    }

    leaf callback {
      description "Callback Fn";
      type string;
    }
    
    leaf results {
      type uint32;
    }
  }

  /*
   * DTS member prepare  response timeout
   */
  notification member-rsp-timeout {
    rwnotify:log-event-id 00030068;
    uses rwlog:severity-error;
    uses dts-xact-attr;
    description "member send response for prep call timeout";
    leaf callback {
      description "callback function";
      type string;
    }
    leaf prep_dispatched {
      description "number of prep calls dispatched";
      type uint32;
    }
  }
  /*
   * Log Keyspec error
   */
  notification notify-keyspec-error {
    rwnotify:log-event-id 00030069;
    description "DTS Keyspec error";
    uses rwlog:severity-error;
    leaf keyspec-error-string {
      description "log message";
      type string;
    }
  }

  /*
   * Log State Change
   */
  notification dts-state-change {
    rwnotify:log-event-id 00030070;
    description "DTS state change log";
    uses rwlog:severity-info;
    leaf dts-member-name {
      type string;
    }
    leaf new-state {
      type string;
    }
  }

  /*
   * Error in setting state
   */
  notification state-change-error {
    rwnotify:log-event-id 00030071;
    description "Log Error in state change";
    uses rwlog:severity-error;
    leaf dts-member-name {
      type string;
    }
    leaf state {
      description "New State for which the error occured";
      type string;
    }
    leaf error-string {
      type string;
    }
  }

  /*
   * Audit missing object in cache
   */
  notification audit-missing-cache {
    rwnotify:log-event-id 00030072;
    description "The object is missing in cache";
    uses rwlog:severity-debug;
    uses dts-reg-attr;

    leaf log {
      description "log message";
      type string;
    }

    leaf obj-keyspec {
      description "Missing keyspec";
      type string;
    }
  }

  /*
   * Audit missing object in DTS
   */
  notification audit-missing-dts {
    rwnotify:log-event-id 00030073;
    description "The cache has  object that is missing in DTS";
    uses rwlog:severity-debug;
    uses dts-reg-attr;

    leaf log {
      description "log message";
      type string;
    }

    leaf obj-keyspec {
      description "Missing keyspec";
      type string;
    }
  }

  /*
   *  The versions of objects mis-match between cache and DTS
   */
  notification audit-mismatch-cache-dts {
    rwnotify:log-event-id 00030074;
    description "The object is different between DTS and cache";
    uses rwlog:severity-debug;
    uses dts-reg-attr;

    leaf log {
      description "log message";
      type string;
    }

    leaf obj-keyspec {
      description "Missing keyspec";
      type string;
    }
  }
  /*
   * DTS API xact keyspec error
   */
  notification xact-keyspec-error {
    rwnotify:log-event-id 00030075;
    description "DTS API trace configured/set event";
    uses rwlog:severity-error;
    uses dts-xact-attr;
    leaf keyspec-error {
      description "Keyspec string";
      type string;
    }
  }

  /*
   * DTS API msg error
   */
  notification msg-unknown-field {
    rwnotify:log-event-id 00030076;
    description "DTS API xact msg unknown field";
    uses rwlog:severity-info;
    uses dts-api-attr;

    leaf msg-info {
      description "msg desc";
      type string;
    }

    leaf log {
      description "msg string";
      type string;
    }

    leaf keyspec {
      description "keyspec";
      type string;
    }
  }

  notification no-schema-no-trace {
    rwnotify:log-event-id 00030077;
    description "DTS API client has no schema";
    uses rwlog:severity-warning;
    uses dts-api-attr;

    leaf log {
       description "msg string";
       type string;
    }
  }

  notification xpath-key-conv-failed {
    rwnotify:log-event-id 00030078;
    description "DTS API xpath to keyspec conv failed";
    uses rwlog:severity-error;
    uses dts-api-attr;

    leaf log {
      description "msg string";
      type string;
    }

    leaf xpath {
      description "xpath";
      type string;
    }
  }

  notification appconf-install-errors {
    rwnotify:log-event-id 00030079;
    description "DTS Appconf install errors";
    uses rwlog:severity-error;
    uses dts-xact-attr;

    leaf count {
      type uint32;
    }

    leaf status {
      description "Return status";
      type uint32;
    }

    leaf err-str {
      type string;
    }
  }

  notification appconf-deinit-missing {
    rwnotify:log-event-id 00030080;
    description "DTS API Appconf deinit missing";
    uses rwlog:severity-warning;
    uses dts-api-attr;

    leaf log {
      description "msg string";
      type string;
    }
  }

  notification xact-delete-failed {
    rwnotify:log-event-id 00030081;
    description "DTS API Xact delete failed";
    uses rwlog:severity-error;
    uses dts-xact-attr;

    leaf log {
      type string;
    }

    leaf reg-id {
      type uint32;
    }
  }

  notification reg-aborted {
    rwnotify:log-event-id 00030082;
    description "Registration aborted";
    uses rwlog:severity-error-critinfo;
    uses dts-api-attr;

    leaf log {
      type string;
    }

    leaf dur {
      type uint32;
    }

    leaf keyspec {
      type string;
    }
  }
  notification api-state-jump {
    rwnotify:log-event-id 00030083;
    description "DTS API State Jump";
    uses rwlog:severity-info;

    leaf client_path {
      type string;
    }

    leaf from-state {
      type string;
    }
    leaf to-state {
      type string;
    }
  }

  notification keyspec-not-in-schema {
    rwnotify:log-event-id 00030084;
    description "Keyspec Does not belong to schema";
    uses rwlog:severity-warning;
    uses dts-api-attr;

    leaf log {
       description "msg string";
       type string;
    }
  }

  notification reg-add-sent-list {
    rwnotify:log-event-id 00030085;
    description "DTS registration added to sent-list";
    uses rwlog:severity-debug;
    uses dts-reg-attr;

    leaf log {
      description "log message";
      type string;
    }
  }

  notification reg-del-keyspec {
    rwnotify:log-event-id 00030086;
    description "DTS deregistration by keyspec";
    uses rwlog:severity-debug;
    uses dts-reg-attr;

    leaf log {
      description "log message";
      type string;
    }
  }

  notification xact-rsp-rcvd {
    rwnotify:log-event-id 00030087;
    description "DTS API Xact response rcvd";
    uses rwlog:severity-debug;
    uses dts-xact-attr;

    leaf log {
      type string;
    }
  }

  notification client-callback-skipped {
    rwnotify:log-event-id 00030088;
    description "client callback skipped";
    uses rwlog:severity-debug;
    uses dts-xact-attr;

    leaf log {
      description "log message";
      type string;
    }
  }

  notification null-msg-rcvd {
    rwnotify:log-event-id 00030089;
    description "Null msg received";
    uses rwlog:severity-debug;
    uses dts-xact-attr;

    leaf log {
      description "log message";
      type string;
    }
  }

  notification split-rsp-dispatch {
    rwnotify:log-event-id 00030090;
    description "Split rsp dispatch async";
    uses rwlog:severity-debug;
    uses dts-xact-attr;

    leaf log {
      description "log message";
      type string;
    }
  }

  notification dispatch-query-rsp {
    rwnotify:log-event-id 00030091;
    description "Query rsp dispatch async";
    uses rwlog:severity-debug;
    uses dts-xact-attr;

    leaf log {
      description "log message";
      type string;
    }
  }

  notification member-rsp-more {
    rwnotify:log-event-id 00030092;
    description "Member responded with more";
    uses rwlog:severity-debug;
    uses dts-xact-attr;

    leaf log {
      description "log message";
      type string;
    }
  }

  notification get-result {
    rwnotify:log-event-id 00030093;
    description "Get result local";
    uses rwlog:severity-debug;
    uses dts-xact-attr;

    leaf log {
      description "log message";
      type string;
    }
  }

  notification reg-not-complete{
    rwnotify:log-event-id 00030094;
    description "Registration not complete";
    uses rwlog:severity-debug;

    uses dts-api-attr;

    leaf log {
      description "log message";
      type string;
    }
  }

  notification reg-complete{
    rwnotify:log-event-id 00030095;
    description "Registration complete";
    uses rwlog:severity-debug;

    uses dts-api-attr;

    leaf log {
      description "log message";
      type string;
    }
  }

  notification audit-done{
    rwnotify:log-event-id 00030096;
    description "Audit complete";
    uses rwlog:severity-debug;

    uses dts-api-attr;

    leaf log {
      description "log message";
      type string;
    }
  }

  notification err-report-xact {
    rwnotify:log-event-id 00030097;
    description "Get result local";
    uses rwlog:severity-debug;
    uses dts-xact-attr;

    leaf log {
      description "log message";
      type string;
    }
  }

  notification xact-ref-incr {
    rwnotify:log-event-id 00030098;
    description "Xact ref cnt incr";
    uses rwlog:severity-debug;
    uses dts-xact-attr;

    leaf log {
      description "log message";
      type string;
    }
  }

  notification xact-ref-decr {
    rwnotify:log-event-id 00030099;
    description "Xact ref cnt decr";
    uses rwlog:severity-debug;
    uses dts-xact-attr;

    leaf log {
      description "log message";
      type string;
    }
  }

  notification block-ref-incr {
    rwnotify:log-event-id 00030099;
    description "Xact block ref cnt incr";
    uses rwlog:severity-debug;
    uses dts-xact-attr;

    leaf log {
      description "log message";
      type string;
    }
  }

  notification block-ref-decr {
    rwnotify:log-event-id 00030100;
    description "Xact block ref cnt decr";
    uses rwlog:severity-debug;
    uses dts-xact-attr;

    leaf log {
      description "log message";
      type string;
    }
  }

  notification appconf-ref-incr{
    rwnotify:log-event-id 00030101;
    description "Appconf ref cnt incr";
    uses rwlog:severity-debug;

    uses dts-api-attr;

    leaf log {
      description "log message";
      type string;
    }
  }

  notification appconf-ref-decr{
    rwnotify:log-event-id 00030102;
    description "Appconf ref cnt decr";
    uses rwlog:severity-debug;

    uses dts-api-attr;

    leaf log {
      description "log message";
      type string;
    }
  }

  notification xactinfo-ref-incr {
    rwnotify:log-event-id 00030103;
    description "Xact-info ref cnt incr";
    uses rwlog:severity-debug;
    uses dts-xact-attr;

    leaf log {
      description "log message";
      type string;
    }
  }

  notification xactinfo-ref-decr {
    rwnotify:log-event-id 00030104;
    description "Xact-info ref cnt decr";
    uses rwlog:severity-debug;
    uses dts-xact-attr;

    leaf log {
      description "log message";
      type string;
    }
  }

  notification qresult-ref-incr {
    rwnotify:log-event-id 00030105;
    description "Query result ref cnt incr";
    uses rwlog:severity-debug;
    uses dts-xact-attr;

    leaf log {
      description "log message";
      type string;
    }
  }

  notification qresult-ref-decr {
    rwnotify:log-event-id 00030106;
    description "Query result ref cnt decr";
    uses rwlog:severity-debug;
    uses dts-xact-attr;

    leaf log {
      description "log message";
      type string;
    }
  }

  notification dts-state-change-advance {
    rwnotify:log-event-id 00030107;
    description "DTS state change, state advance";
    uses rwlog:severity-info;
    uses dts-api-attr;
    leaf state {
      description "This state had nothing afoot";
      type string;
    }
  }

  notification appconf-install-failed {
    rwnotify:log-event-id 00030108;
    description "DTS Appconf install event failure";
    uses rwlog:severity-error;
    uses dts-xact-attr;

    leaf log {
      type string;
    }

    leaf err_ct {
      type uint32;
    }

    leaf callback {
      description "Callback fn";
      type string;
    }

    leaf client {
      description "Client path";
      type string;
    }
  }

  notification appconf-error {
    rwnotify:log-event-id 00030109;
    description "DTS Appconf install event failure";
    uses rwlog:severity-error;
    uses dts-xact-attr;

    leaf log {
      type string;
    }
    leaf client {
      type string;
    }

  }

  notification delete-non-existent {
    rwnotify:log-event-id 00030110;
    description "DTS attempting to delete non-existent data";
    uses rwlog:severity-debug;
    uses dts-xact-attr;

    leaf log {
      type string;
    }
    leaf client {
      type string;
    }
    leaf reg-kstr {
      type string;
    }
    leaf kstr {
      type string;
    }
  }

  notification trace-prepcheck-timeout {
    rwnotify:log-event-id 00030111;
    description "Prepare cb timeout at member";
    uses rwlog:severity-critical;
    leaf xact-id          { type string; }
    leaf member           { type string; }
  }

  notification config-ready-monitor {
    rwnotify:log-event-id 00030112;
    description "Still waiting for all config-ready tasks to reach RUNNING state";
    uses rwlog:severity-info-critinfo;
    leaf waiting-on {
      description "Still waiting on these tasks";
      type string;
    }
  }

} // module rw-dts-api-log
