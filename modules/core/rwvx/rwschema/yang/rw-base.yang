/*
 * 
 * (c) Copyright RIFT.io, 2013-2016, All Rights Reserved
 *
 *
 */

module rw-base
{
  namespace "http://riftio.com/ns/riftware-1.0/rw-base";
  prefix "rw-base";

  import rw-pb-ext {
    prefix "rwpb";
  }

  import rw-yang-types {
    prefix rwt;
  }

  import rw-cli-ext {
    prefix "rwcli";
  }

  import rwvcs-types {
    prefix "rwvcstypes";
  }

  revision 2014-05-29 {
    description
      "Initial revision. This YANG file defines common groupings, typedefs, and
       containers available on Riftware";
    reference
      "Derived from earlier versions of base YANG files";
  }

  typedef log-level {
    description
      "Different logging levels that can be set for the fpath
       application ";
    type enumeration {
      enum disable;
      enum emergency;
      enum alert;
      enum critical;
      enum error;
      enum warn;
      enum notice;
      enum crit-info;
      enum info;
      enum debug;
    }
  }

  typedef category_type {
    description
      "Different Riftware categories";
    type enumeration {
      enum scheduler;
      enum cli;
      enum ncclntlib;
      enum fastpath;
    }
  }

  typedef state_type {
    type enumeration {
      enum CRASHED;
      enum LOST;
      enum STOPPING;
      enum STOPPED;
      enum STARTING;
      enum INITIALIZING;
      enum RECOVERING;
      enum RUNNING;
      enum TO_RECOVER;
      /* Also new states to waitstates[] in rwdts_api.c */
    }
  }


  typedef cpu-percentage {
    description "A type to use for CPU utilization percentages.  Note that this
        may go over 100% on multicore systems.";

    type decimal64 {
      fraction-digits 7;
    }
  }

  container version {
    config false;
    rwpb:msg-new Version;
    description "Riftware version information";

    leaf version {
      type string;
      description "Riftware version";
    }

    leaf build_sha {
      type string;
      description "Git sha";
    }

    leaf build_date {
      type string;
      description "Build date";
    }
  }

  container uptime {
    config false;
    rwpb:msg-new Uptime;
    description "Riftware system uptime information";

    leaf uptime {
      type uint64;
      description "System uptime";
    }

    leaf days {
      description "System uptime - days";
      type uint32;
    }

    leaf hours {
      description "System uptime - hours";
      type uint32;
    }

    leaf minutes {
      description "System uptime - minutes";
      type uint32;
    }

    leaf seconds {
      description "System uptime - seconds";
      type uint32;
    }

  }

  container vcs {
    description "Riftware resource management is centered around the VCS.";

    container info {
      config false;
      rwpb:msg-new VcsInfo;
      description "Provides tasklet related information";

      grouping collection_info {
        container collection_info {
          description "Rift collection information";
          rwpb:msg-new CollectionInfo;

          leaf collection-type {
            description "Collection Type";
            type string;
          }
        }
      }

      grouping vm_info {
        container vm_info {
          description "Rift VM information";
          rwpb:msg-new VmInfo;

          leaf vm-ip-address {
            description "RWVM IP address";
            type rwt:ip-address;
            rwpb:field-string-max 46;
          }

          leaf pid {
            description "Process ID";
            type uint32;
          }

          leaf lpid {
            description "Local Process ID";
            type uint32;
          }

          leaf leader {
            description "True if this VM is designated as a leader for the parent collection.";
            type boolean;
          }
        }
      }

      grouping proc_info {
        container proc_info {
          description "";
          rwpb:msg-new ProcInfo;

          leaf pid {
            description "Process ID";
            type uint32;
          }

          leaf native {
            description "Native Linux Process";
            type boolean;
            default false;
          }

        }
      }

      grouping component_info {
        list component_info {
          description "";
          key "instance_name";
          rwpb:msg-new ComponentInfo;
          config false;

          leaf component_type {
            description "";
            type rwvcstypes:component_type;
          }

          leaf component_name {
            description "";
            type string;
          }

          leaf instance_id {
            description "";
            type uint64;
          }

          leaf instance_name {
            description "";
            type string;
          }

          leaf state {
            description "Current component state";
            type state_type;
          }

          leaf config-ready {
            description "Config readiness check state";
            type boolean;
            default false;
          }

          leaf recovery-action {
            description "Defined recovery action if this component fail";
            type rwvcstypes:recovery-type;
          }

          leaf rwcomponent_parent {
            description "";
            type leafref {
              path "../../../components/component_info/instance_name";
            }
          }

          leaf-list rwcomponent_children {
            description "";
            type leafref {
              path "../../../components/component_info/instance_name";
            }
          }

          choice component_info {
            case collection_info {
              uses collection_info;
            }
            case vm_info {
              uses vm_info;
            }
            case proc_info {
              uses proc_info;
            }
          }
        }
      }

      container components {
        uses component_info;
      }
    }

    container resource {
      container utilization {
        description "The resources that are used by each vm";
        rwpb:msg-new VcsResource;
        config false;

        list vm {
          description "Each VM Instance resource usage";
          key "id";

          leaf id {
            description "A unique identifier assigned to the VM. This is initially
                         assigned in the manifest";

            type uint32;
          }

          container cpu {
            description "The utlization of CPU on the VM";

            container aggregate {
              description "CPU utlization aggregated over all available CPU";

              leaf user {
                type cpu-percentage;
              }

              leaf system {
                type cpu-percentage;
              }

              leaf idle {
                type cpu-percentage;
              }
            }

            list individual {
              key "id";

              leaf id {
                type uint8;
                description "CPU ID";
              }

              leaf user {
                type cpu-percentage;
              }

              leaf system {
                type cpu-percentage;
              }

              leaf idle {
                type cpu-percentage;
              }
            }
          }

          container memory {
            leaf curr-usage {
              description "The physical memory available to the VM that is currently used";

              type uint32;
              units "kB";
            }

            leaf total {
              description "The physical memory available to the VM";

              type uint32;
              units "kB";
            }
          }

          container storage {
            leaf curr-usage {
              description "The secondary memory available to the VM that is currently used";

              type uint32;
              units "kB";
            }

            leaf total {
              description "The secondary memory available to the VM";

              type uint32;
              units "kB";
            }
          }

          list processes {
            rwpb:msg-new VcsProcess;
            key "instance-name";

            leaf instance-name {
              description "Process instance-name";
              type string;
            }

            leaf file-descriptors {
              description "Number of open file";
              type uint32;
            }

            leaf cpu {
              description "CPU utilization";
              type cpu-percentage;
            }

            leaf memory {
              description "Resident physical memory";
              type uint32;
              units "kB";
            }

            leaf thread-count {
              description "Number of threads in this process";
              type uint32;
            }
            list tasklets {
              rwpb:msg-new ProcessTasklet;
              key "tasklet-name";

              leaf tasklet-name {
                description "Tasklet name";
                type string;
              }
            }
          }

          list tasklets {
            rwpb:msg-new VMTasklet;
            key "tasklet-name";

            leaf tasklet-name {
              description "Tasklet name";
              type string;
            }
          }
        }
      }
    } // container vcs.resources
    
    container proc_heartbeat {
      description "RWProc heartbeat parameters";
      rwpb:msg-new ProcHeartbeat;

      leaf tolerance {
        description "Maximum number of consecutive missed heartbeats";
        type uint32;
        default 600;
      }

      leaf frequency {
        description "Number of heartbeats sent per second";
        type uint16;
        default 10;
      }

      leaf enabled {
        description "Heartbeating enabled";
        type boolean;
        default true;
      }

      list stats {
        description "Statistics gathered regarding process heartbeats";
        key "instance-name";
        config false;
        rwpb:msg-new ProcHeartbeatStats;

        leaf instance-name {
          type string;
          description "Instance name of process being monitored";
        }

        leaf init-duration {
          type decimal64 {
            fraction-digits 17;
          }
          description "Time from monitoring being started until first heartbeat was received";
        }

        list timing {
          key "id";

          leaf id {
            type uint32;
          }

          leaf recv-time {
            type decimal64 {
              fraction-digits 17;
            }
            description "Times at which heartbeats were received";
          }

          leaf send-time {
            type decimal64 {
              fraction-digits 17;
            }
            description "Times as which heartbeats were sent";
          }

          leaf missed {
            type uint32;
            description "Number of time this heartbeat was not received when expected";
          }
        }

        container missed-histogram {
          leaf interval-duration {
            type uint32;
            description "Number of seconds of data each inverval in the histogram contains";
          }

          leaf-list histogram {
            // This should be a real list as leaf-lists only take unique values.
            // However, the author (me) is lazy and whiny and doesn't want to deal
            // with more allocations inside of a nested loop, so:  RIFT-7448.
            type uint32;
          }
        }
      }
    }
    grouping publish-state-group {
      container publish-state {
        leaf state {
          description "component state";
          type state_type;
        }
        leaf config-ready {
          description "Config readiness check state";
          type boolean;
          default false;
        }
        leaf recovery-action {
          description "Defined recovery action if this component fail";
          type rwvcstypes:recovery-type;
        }
      }
    }

    container instances {
      description "The VCS instances in the system";
      rwpb:msg-new VcsInstance;
      config false;

      list instance {
        description "The VCS instances in the system";
        key "instance-name";

        leaf instance-name {
          description "Instance-name to stop";
          type string;
        }

        leaf admin-stop {
          description "Stop this instance";
          type boolean;
        }

        list child-n {
          description "A list of child instances";
          key "instance-name";
          leaf instance-name {
            description "Instance-name of the child";
            type string;
          }

          leaf component-name {
            description "component-name of the child";
            type string;
          }

          leaf ip-address {
            description "ip-address of the VM where to start the component";
            type string;
          }

          leaf component-type {
            description "";
            type rwvcstypes:component_type;
          }
          uses publish-state-group;

          leaf admin-command {
            description "Admin state of the child instance";
            type enumeration {
              enum START;
              enum STOP;
              enum RECOVER;
            }
          }
        }
      }
    } //list of instances

  } // container vcs

  rpc tracing {
    description "Sets the logging related parameters";
    input {
      container set {
        rwpb:msg-new RwTracing;
        rwpb:msg-flat true;
        rwpb:field-inline "true";

       leaf level {
         description
             "Specify logging level - Allowed values are emergency, alert,
             critical, error, warn, notice, info, debug";

         type log-level;
       }
      }
    }
  }

  container return_status {
    rwpb:msg-new ReturnStatus;
    rwpb:msg-flat true;
    rwpb:field-inline "true";
    config "false";

    leaf error_number {
      type int32;
      description "Error number";
    }
    leaf error_string {
      type string;
      rwpb:field-string-max 128;
      description "Error string value";
    }
  }

}
