/*
 * 
 * (c) Copyright RIFT.io, 2013-2016, All Rights Reserved
 *
 *
 */

module rwvcs-types
{
  namespace "http://riftio.com/ns/riftware-1.0/rwvcs-types";
  prefix "rwvcstypes";

  import rw-pb-ext { 
    prefix "rwpb"; 
  }

  import rw-yang-types { 
    prefix "rwt"; 
  }

  import ietf-inet-types { 
    prefix "inet"; 
    revision-date 2013-07-15; 
  }

  revision 2014-03-12 {
    description
      "Initial implementation of RW.Manifest.";
    reference
      "RW.VX Software Component Document";
  }

  typedef component_type {
    type enumeration {
      enum RWCOLLECTION;
      enum RWVM;
      enum RWPROC;
      enum PROC;
      enum RWTASKLET;
    }
  }

  typedef recovery-type {
    type enumeration {
      enum NONE;
      enum RESTART;
      enum FAILCRITICAL;
      enum IGNORE;
      enum CUSTOM;
    }
  }

  grouping rwvcs-variable-list {
    leaf-list python-variable {
      description 
          "List of Python variable assignments";
      type string;
    }
  }

  grouping valgrind {
    container valgrind {
      leaf enable {
        description 
            "Run the component under valgrind";
        type boolean;
      }

      leaf-list opts {
        description 
            "Command line options to pass to valgrind";
        type string;
      }
    }
  }

  grouping action-list {
    list action {
      description 
          "This section contains a sequence 
           of RW.VCS actions";
      key "name";
      rwpb:msg-new VcsAction;

      leaf name {
        description 
            "Name of the action within the sequence";
        type string;
      }

      grouping rwvcs-python-loop {
        leaf python-loop-expression {
          description "Python expression";
          type string;
        }

        leaf python-loop-iterate {
          description "Python iteration";
          type string;
        }
      }
      uses rwvcs-python-loop;

      choice action {
        case annex {
          container annex {
            leaf component-name {
              description 
                  "Name of the component type 
                   in the inventory";
              type leafref {
                path "../../../../../../../component/component-name";
              }
            }
            leaf instance-id {
              description 
                  "ID of the component instance 
                   in the inventory";
              type string;
            }
          }
        }

        case start {
          container start {
            rwpb:msg-new ActionStart;

            uses rwvcs-variable-list;
            leaf component-name {
              description 
                  "Name of the component type in 
                   the inventory";
              type leafref {
                path "../../../../../../../component/component-name";
              }
            }
            leaf instance-id {
              description 
                  "ID of the component instance 
                   in the inventory";
              type string;
            }
            leaf config-ready {
              description 
                  "Config readiness check enable";
              type boolean;
              default true;
            }
            leaf recovery-action {
              description 
                  "Define recovery action if this component fail";
              type recovery-type;
            }
          }
        }

        case sleep {
          container sleep {
            leaf wait-time-usec {
              description 
                  "Time to wait while sleeping";
              type uint32;
            }
          }
        }
      } // choice action
    } // list action
  } // grouping action-list

  grouping rwvcs-event-list {
    container event-list {
      description "";
      rwpb:msg-new VcsEventList;

      list event {
        description 
            "This section contains a list 
             of RW.VCS events";
        key "name";
        rwpb:msg-new VcsEvent;

        leaf name {
          description 
              "Name of the event";
          type string;
        }

        uses action-list;
      } // list event
    } // container event-list
  } // grouping rwvcs-event-list

  grouping rwvcs-rwcollection {
    container rwcollection {
      description 
          "This section defines a RW.VCS 
           rwollection component";
      rwpb:msg-new VcsRwCollection;

      leaf collection-type {
        description "Collection type";
        type string;
      }

      uses rwvcs-event-list;
    }
  }

  grouping rwvcs-rwvm {
    container rwvm {
      description 
          "This section defines a RW.VCS 
           rwvm component";
      rwpb:msg-new VcsRwVm;

      leaf pool-name {
        description 
            "Name of the pool from which to 
             allocate the VM";
        type string;
      }

      leaf leader {
        description
            "True if this VM is designated as a leader for
             the parent collection.";
        type boolean;
      }

      uses rwvcs-event-list;
      uses valgrind;
    }
  }

  grouping rwvcs-rwproc {
    container rwproc {
      description 
          "This section defines a RW.VCS 
           rwproc component";
      rwpb:msg-new VcsRwproc;

      leaf run-as {
        description
            "Host OS user that should run this 
             process, requires sudo -E access 
             and non-collapsed processes";
        type string;
      }

      list tasklet {
        description 
            "List of tasklets to be run within 
             this process";
        key "name";
        rwpb:msg-new RwprocTasklet;

        leaf name {
          description 
              "Local description of the tasklet";
          type string;
        }

        leaf component-name {
          description 
              "Component name of the tasklet";
          mandatory true;
          type string;
        }

        leaf instance-id {
          description
              "If specified, the desired instance-id of
               tasklet component instance";
          type uint32;
        }

        leaf config-ready {
          description 
              "Config readiness check enable";
          type boolean;
          default true;
        }

        leaf recovery-action {
          description 
              "Define recovery action if this component fail";
          type recovery-type;
        }

        uses rwvcs-variable-list;
      }
      uses valgrind;
    }
  }

  grouping native-proc {
    container native-proc {
      rwpb:msg-new NativeProc;

      leaf run-as {
        description 
            "Host OS user that should run this 
             process, requires sudo -E access";
        type string;
      }

      leaf environment {
        description 
            "Runtime environment for native process";
        type string;
      }

      leaf exe-path {
        description 
            "Path to native process executable";
        type string;
      }

      leaf args {
        description 
            "Arguments to pass to native process";
        type string;
      }

      leaf network-namespace {
        description 
            "Namespace to start process in";
        type string;
      }

      leaf stdout {
        description 
            "Redirect stdout to the file at the 
             specified path";
        type string;
      }

      leaf stderr {
        description 
            "Redirect stderr to the file at the 
             specified path. Optionally, 'stdout' 
             may be used to redirect to the same 
             file as stdout";
        type string;
      }

      leaf interactive {
        description "Native process is interactive and needs
          terminal control";
        type empty;
      }
      uses valgrind;
    }
  }

  grouping rwvcs-rwtasklet {
    container rwtasklet {
      description 
          "This section defines a RW.VCS 
           rwtasklet component";
      rwpb:msg-new VcsRwTasklet;

      leaf plugin-directory {
        description "";
        type string;
      }

      leaf plugin-name {
        description "";
        type string;
      }

      leaf plugin-version {
        description "";
        type string;
      }
    }
  }

  grouping rwvcs-component-list {
    list component {
      description 
          "This section defines the RIFT.ware 
           virtual components";
      key "component-name";
      rwpb:application-request-point;

      leaf component-name {
        description "";
        type string;
      }

      leaf component-type {
        description "";
        type component_type;
        mandatory true;
      }

      choice component {
        case rwvcs-rwcollection {
          uses rwvcs-rwcollection;
        }
        case rwvcs-rwvm {
          uses rwvcs-rwvm;
        }
        case rwvcs-rwproc {
          uses rwvcs-rwproc;
        }
        case native-proc {
          uses native-proc;
        }
        case rwvcs-rwtasklet {
          uses rwvcs-rwtasklet;
        }
      }
    } // list component
  } // grouping rwvcs-component-list
}

// vim: sw=2
