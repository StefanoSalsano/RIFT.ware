/*
 * 
 * (c) Copyright RIFT.io, 2013-2016, All Rights Reserved
 *
 *
 */

module rw-vnf-base-config
{
  namespace "http://riftio.com/ns/riftware-1.0/rw-vnf-base-config";
  prefix "rwvnfbase";

  import rw-pb-ext {
    prefix "rwpb";
  }

  import rw-cli-ext {
    prefix "rwcli";
  }

  import mano-base {
    prefix "manobase";
  }
  import rw-yang-types {
    prefix "rwt";
  }
  import rw-vnf-base-types {
    prefix "rwvnfbasetypes";
  }

  revision 2015-08-25 {
    description
      "This conatins common objects for RIFT VNFs. The
       RIFT VNFs augment this YANG model for configuration.";
  }

  grouping vm-identity {
    leaf vm-identity {
      description "VM ID";
      type uint32;
    }
  }

//port groupings

  augment /manobase:vnf-config/manobase:vnf {
    description
      "Container for VNF base configuration";
    container fabric {
      list ip {
        rwpb:msg-new ConfigFabricIp;
        key "subnet";
        leaf subnet{
          description "IP address assigned to the interface";
          type rwt:ip-prefix-non-canonical;
          rwpb:field-string-max 46;
          rwpb:field-inline true;
          rwpb:field-c-type "rw_ip_prefix_t";
        }
      }
    }
    
    list network-context {
      description "Network Context configuration";
      rwpb:msg-new ConfigNetworkContext;
      rwcli:new-mode "network-context";
      key name;
      leaf name {
        description "Name of Network-context";
        rwpb:field-inline true;
        type string {
          length "min..64";
        }
      }

      list interface {
        description "List of interfaces";
        rwpb:msg-new ConfigIpInterface;
        rwcli:new-mode "ip-interface";
        key name;

        leaf name {
          description "Interface name";
          type string {
            length "min..64";
          }
          rwpb:field-inline true;
        }
        leaf interface-type {
          description "Interface type, defaults to an interface bound to port/VLAN";
          type rwvnfbasetypes:interface-type;
        }

        choice type {
          case broadcast {
            uses rwvnfbasetypes:bind-interface;
          }
          case tunnel {
            container tunnel {
              rwpb:msg-flat true;
              rwpb:msg-new TunnelParams;
              uses rwvnfbasetypes:tunnel-params;
            }
          }
        }
        choice autoconfig{
          case autoconfig{
            container autoconfigure {
              description "Auconfigure paramertes either from port or dhcp";
              leaf port{
                type empty;
              }
            }
          }
          case manual {
            list ip {
              key address;
              
              leaf address {
                description "IP address assigned to the interface";
                type rwt:ip-prefix-non-canonical;
                rwpb:field-string-max 46;
                rwpb:field-inline true;
                rwpb:field-c-type "rw_ip_prefix_t";
              }
            }
          }
        }
      }
      container ipv6{
        description "Ipv6 specific configuration. Routes/Neighbors are common to v4/v6 and are found under the ip container";
        leaf forwarding{
          type empty;
        }
      }
      container ip {
        description "IP configuration parameters";
        rwpb:msg-new ConfigIp;
        leaf ipv6-forwarding {
          type empty;
          description "Enable IPv6 forwarding";
        }

        list route {
          description "Static IP route configured";
          rwpb:msg-new ConfigRoute;
          key prefix;
          rwcli:new-mode "ip-route";
          leaf prefix {
            description "static IP route prefix";
            type rwt:ip-prefix-non-canonical;
            rwpb:field-string-max 46;
          }
          uses rwvnfbasetypes:next-hop-content;
        }
        
        list neighbor {
          description "Neighbor (ARP) configuration";
          key address;

          leaf address {
            description "IP address for the static ARP entry";
            type rwt:ip-address;
            rwpb:field-string-max 46;
            rwpb:field-c-type "rw_ip_addr_t";
          }
          leaf macaddress {
            description "MAC address for the static ARP entry";
            type rwt:mac-address;
            rwpb:field-string-max 18;
            rwpb:field-c-type "rw_mac_addr_t";
          }
          leaf interface-name {
            description "Interface Name for the static ARP entry";
            type string {
              length "min..64";
            }
          }
        }

        list pool {
          description "IP pool configuration";
          rwpb:msg-new ConfigPool;
          rwcli:new-mode "ip-pool";
          key name;

          leaf name {
            description "Name for the pool";
            type string {
              length "min..64";
            }
          }
          leaf nat-pool {
            description "Enable NAT for the pool";
            type boolean;
          }
          list address {
            description "List of IP prefixes for the pool";
            rwpb:msg-new ConfigPoolAddress;
            key prefix;
            leaf prefix {
              description "Prefix for the pool";
              rwpb:field-inline true;
              type rwt:ip-prefix-non-canonical;
              rwpb:field-string-max 46;
              rwpb:field-c-type "rw_ip_prefix_t";
            }
          }
        }

        list nat-pool {
          description "NAT pool configuration";
          rwpb:msg-new ConfigNatPool;
          rwcli:new-mode "ip-nat-pool";
          key name;
          leaf name {
            description "Name for the NAT pool";
            type string {
              length "min..64";
            }
          }
          list address {
            description "List of IP prefixes for the pool";
            rwpb:msg-new ConfigNatPoolAddress;
            max-elements 10;
            key prefix;
            leaf prefix {
              description "Prefix for the NAT pool";
              rwpb:field-inline true;
              type rwt:ip-prefix-non-canonical;
              rwpb:field-string-max 46;
              rwpb:field-c-type "rw_ip_prefix_t";
            }
          }
        }

      }

      container packet-capture {
        description "Packet capture configuration";
        list filter {
          rwpb:msg-new IpFilterConfig;
          key "trace-id";
          uses rwvnfbasetypes:fpath-packet-debug-params;
        }
      }

      container packet-trace {
        description "Packet trace configuration";
        list filter {
          rwpb:msg-new IpFilterConfigTrace;
          key "trace-id";
          uses rwvnfbasetypes:fpath-packet-debug-params;
        }
      }

      list vrf {
        description "Virtual Router and Forwarding (VRF) configurations";
        rwpb:msg-new ConfigVrf;
        rwcli:new-mode vrf;

        key name;
        max-elements 32;
        leaf name {
          description "Name of VRF";
          rwpb:field-inline true;
          type string {
            length "min..64";
          }
        }

        list interface {
          description "VRF interface configuration";
          rwpb:msg-new VrfConfigIpInterface;
          rwcli:new-mode "ip-interface";
          key name;

          leaf name {
            description "Interface name";
            type string {
              length "min..64";
            }
            rwpb:field-inline true;
          }
          leaf interface-type {
            description "Interface type, defaults to an interface bound to port/VLAN";
            type rwvnfbasetypes:interface-type;
          }

          choice type {
            case broadcast {
              uses rwvnfbasetypes:bind-interface;
            }
            case tunnel {
              container tunnel {
                rwpb:msg-flat true;
                rwpb:msg-new VrfTunnelParams;
                uses rwvnfbasetypes:tunnel-params;
              }
            }
          }

          list ip {
            description "Interface IP list";
            key address;

            leaf address {
              description "IP address assigned to the interface";
              type rwt:ip-prefix-non-canonical;
              rwpb:field-string-max 46;
              rwpb:field-inline true;
              rwpb:field-c-type "rw_ip_prefix_t";
            }
          }
        }
        container ipv6{
          description "Ipv6 specific configuration. Routes/Neighbors are common to v4/v6 and are found under the ip container";
          leaf forwarding {
            type empty;
            description "Enable IPv6 forwarding";
          }
        }
        container ip {
          description "VRF IP configuration";
          rwpb:msg-new VrfConfigIp;
          leaf ipv6-forwarding {
            type empty;
            description "Enable IPv6 forwarding";
          }
          list route {
            description "Static IP routes configured";
            rwpb:msg-new VrfConfigRoute;
            key prefix;
            rwcli:new-mode "ip-route";
            leaf prefix {
              description "Static IP route prefix";
              type rwt:ip-prefix-non-canonical;
              rwpb:field-string-max 46;
            }
            list nexthop {
              description "Next hops in the route";
              rwpb:msg-new VrfConfigNexthop;
              max-elements 10;
              key "gateway interface-name";

              leaf gateway {
                rwpb:field-inline true;
                description "Gateway address of the static route";
                type rwt:ip-address;
                rwpb:field-string-max 46;
                rwpb:field-c-type "rw_ip_addr_t";
              }
              leaf interface-name {
                rwpb:field-inline true;
                description "Interface of the static route";
                type string {
                  length "min..64";
                }
                rwpb:field-inline true;
              }
            }
          }

          list neighbor {
            description "Neighbor (ARP) configuration";
            key address;

            leaf address {
              description "IP address for the static ARP entry";
              type rwt:ip-address;
              rwpb:field-string-max 46;
              rwpb:field-c-type "rw_ip_addr_t";
            }
            leaf macaddress {
              description "MAC address for the static ARP entry";
              type rwt:mac-address;
              rwpb:field-string-max 18;
              rwpb:field-c-type "rw_mac_addr_t";
            }
            leaf interface-name {
              description "Interface Name for the static ARP entry";
              type string {
                length "min..64";
              }
            }
          }

          list pool {
            description "IP pool configuration";
            rwpb:msg-new VrfConfigPool;
            rwcli:new-mode "ip-pool";
            key name;

            leaf name {
              description "Name for the pool";
              type string {
                length "min..64";
              }
            }
            leaf nat-pool {
              description "Enable NAT for the pool";
              type boolean;
            }
            list address {
              description "List of IP prefixes for the pool";
              rwpb:msg-new VrfConfigPoolAddress;
              key prefix;
              leaf prefix {
                description "Prefix for the pool";
                rwpb:field-inline true;
                type rwt:ip-prefix-non-canonical;
                rwpb:field-string-max 46;
                rwpb:field-c-type "rw_ip_prefix_t";
              }
            }
          }

          list nat-pool {
            description "NAT pool configuration";
            rwpb:msg-new VrfConfigNatPool;
            rwcli:new-mode "ip-nat-pool";
            key name;
            leaf name {
              description "Name for the NAT pool";
              type string {
                length "min..64";
              }
            }
            list address {
              rwpb:msg-new VrfConfigNatPoolAddress;
              max-elements 10;
              key prefix;
              leaf prefix {
                description "Prefix for the NAT pool";
                rwpb:field-inline true;
                type rwt:ip-prefix-non-canonical;
                rwpb:field-string-max 46;
                rwpb:field-c-type "rw_ip_prefix_t";
              }
            }
          }

        }

        container packet-capture {
          description "Packet capture configuration";
          list filter {
            rwpb:msg-new VrfIpFilterConfig;
            key "trace-id";
            uses rwvnfbasetypes:fpath-packet-debug-params;
          }
        }

        container packet-trace {
          description "Packet trace configuration";
          list filter {
            rwpb:msg-new VrfIpFilterConfigTrace;
            key "trace-id";
            uses rwvnfbasetypes:fpath-packet-debug-params;
          }
        }
      }
    }

    list port {
      description "Port configuration";
      rwcli:new-mode " port";
      rwpb:msg-new PortConfig;
      max-elements 64;
      key name;

      leaf name {
        description "Name of the port";
        rwpb:field-inline true;
        type string {
          length "min..64";
        }
      }
      leaf port-type {
        description "Type of port (ethernet/bundle-ether)";
        type rwvnfbasetypes:port-type;
      }

      leaf descr-string {
        description "Description comment for port";
        rwpb:field-inline true;
        type string {
          length "min..32";
        }
      }

      leaf open {
        description "Administrative bring up  the port";
        type empty;
      }
      leaf mtu {
        description "MTU of the port";
        type uint32;
      }
      choice porttype {
        description "Port type";
        case ethernet {
          description "Ethernet port configuration";
          leaf virtual-fabric {
            type boolean;
          }
          container port-identity {
            uses vm-identity;
            choice type {
              case ip-address {
                leaf ip-address {
                  description "Cloud assigned IP address for this port";
                  rwpb:field-inline true;
                  type rwt:ip-address;
                  rwpb:field-string-max 46;
                  rwpb:field-c-type "rw_ip_addr_t";
                }
              }
              case pci-address {
                leaf pci-name {
                  description "PCI address of the port";
                  type string {
                    length "min..12";
                    pattern "[0-9]{4}:[0-9]{2}:[0-9]{2}\.[0-9]";
                  }
                }
              }
              case interface-name {
                leaf interface-name {
                  description "Port name in the VM (shown in ifconfig)";
                  type string {
                    length "min..16";
                  }
                }
              }
              case private-name {
                leaf private-name {
                  description "Internal DPDK name of the port";
                  type string;
                }
              }
            }
            leaf port-mode {
              description "Mode of operation for port (raw-socket/direct)";
              type rwvnfbasetypes:port-mode;
            }
          }
          container vlan-offload{
            leaf rx-strip{
              description "Configure the hardware to strip vlan header. Please note that this is on the receive path for vlan packets";
              type empty;
            }
          }

          container application{
            description "Application that is using this port. Default is IPFP";
            leaf rx {
              description "Application name receiving the packets on the port";
              rwpb:field-inline true;
              type string {
                length "min..32";
              }
            }
            leaf tx {
              description "Application name transmitting the packets on the port";
              rwpb:field-inline true;
              type string {
                length "min..32";
              }
            }
          }
          container bundle-member {
            description "Port aggreagation configuration";
            leaf name {
              description "Name of the port";
              rwpb:field-inline true;
              type string {
                length "min..64";
              }
            }
            leaf mode {
              description "LACP mode";
              type rwvnfbasetypes:lacp-mode;
            }
            container port {
              leaf priority {
                description "Port priority";
                type uint32;
              }
            }
          }
          container lacp {
            description "LACP configuration";
            leaf fast-switchover {
              description "Used to disable the wait-while timer in LACP state machine";
              type empty;
            }
            leaf rate {
              description "LACP PDU rate (fast/slow)";
              type rwvnfbasetypes:lacp-rate;
            }
          }
          leaf receive-q-length {
            description "Number of receive queues for the port. Default is 2";
            type uint32;
          }

          container descriptors {
            leaf rx-size {
              description "Size of rx descriptor ring. Default is 256";
              type uint32;
            }
            leaf tx-size {
              description "Size of tx descriptor ring. Default is 256";
              type uint32;
            }
          }
          leaf numa-socket {
            type int32;
            description "CPU NUMA socket where the port is attached";
          }

          // Flow control configuration for the port
          uses rwvnfbasetypes:flow-control;
        }
        case lag {
          description "Link Aggregateion Group (LAG) configuration";
          container lacp-attributes {
            leaf priority {
              description "Configure the LACP priority for the VNF";
              type uint32;
            }
            leaf mac {
              description "MAC address used by the Link Aggregation Group";
              type rwt:mac-address;
              rwpb:field-string-max 18;
              rwpb:field-c-type "rw_mac_addr_t";
            }
          }
          container minimum-active {
            leaf links {
              description "Minimum number of active links to bring up the bundle";
              type uint32{
                range "1..16";
              }
            }
          }
          container maximum-active {
            leaf links {
              description "Maximum number of active links in the bundle";
              type uint32{
                range "1..16";
              }
            }
          }
          leaf load-balance {
            description "Packet contents to use for load-balancing";
            type rwvnfbasetypes:lag-lb-mode;
          }
          leaf mac-mode {
            description "Mac-mode for 1:1 redundancy";
            type rwvnfbasetypes:mac-mode;
          }
        }
      }

      list vlan {
        description "VLAN configuration";
        key id;
        rwcli:new-mode "  vlan";
        rwpb:msg-new VlanConfig;
        max-elements 32;

        leaf id {
          description "VLAN ID";
          type uint32;
        }
        leaf descr-string {
          description "Description comment for VLAN";
          rwpb:field-inline true;
          type string {
            length "min..32";
          }
        }

        leaf open {
          description "Open the specified VLAN";
          type empty;
        }

        leaf virtual-fabric {
          type boolean;
        }
      }
    }

    container virtual-fabric {
      description "Virtual fabric configuration";
      list network {
        description "Network configuration";
        key address;

        leaf address {
          description "IP address assigned to the interface";
          type rwt:ip-prefix;
          rwpb:field-string-max 46;
          rwpb:field-inline true;
          rwpb:field-c-type "rw_ip_prefix_t";
        }
      }
    }

    /*Temporary*/
    container cat {
      rwpb:msg-new RwCat;
      leaf host {
        type rwt:ip-address;
        rwpb:field-string-max 46;
        description "Host address of CAT instance";
      }
    }

    container noisy-neighbor {
      rwpb:msg-new RwNoisyNeighbor;
      leaf enable {
        type boolean;
        description "Enable the noisy neighbor on this colony";
      }
    }

  }
}
