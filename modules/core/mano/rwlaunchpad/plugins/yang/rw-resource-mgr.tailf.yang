/*
 * 
 * (c) Copyright RIFT.io, 2013-2016, All Rights Reserved
 *
 *
 */

module rw-resource-mgr-annotation
{
  namespace "http://riftio.com/ns/riftware-1.0/rw-resource-mgr-annotation";
  prefix "rw-resource-mgr-ann";

  import rw-resource-mgr
  {
    prefix rw-resource-mgr;
  }

  import tailf-common {
    prefix tailf;
  }

  tailf:annotate "/rw-resource-mgr:resource-pool-records" {
    tailf:callpoint base_show;
  }

  tailf:annotate "/rw-resource-mgr:resource-mgmt" {
    tailf:callpoint base_show;
  }
}
