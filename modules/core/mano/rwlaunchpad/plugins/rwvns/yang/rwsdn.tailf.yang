/*
 * 
 * (c) Copyright RIFT.io, 2013-2016, All Rights Reserved
 *
 *
 */

module rwsdn-annotation
{
  namespace "http://riftio.com/ns/riftware-1.0/rwsdn-annotation";
  prefix "rwsdn-ann";

  import rwsdn {
    prefix rwsdn;
  }
}
