/*
 * 
 * (c) Copyright RIFT.io, 2013-2016, All Rights Reserved
 *
 *
 */

module nsd
{
  namespace "urn:ietf:params:xml:ns:yang:nfvo:nsd";
  prefix "nsd";

  import rw-pb-ext {
    prefix "rwpb";
  }

  import vld {
    prefix "vld";
  }

  import vnfd {
    prefix "vnfd";
  }

  import ietf-inet-types {
    prefix "inet";
  }

  import ietf-yang-types {
    prefix "yang";
  }

  import mano-types {
    prefix "manotypes";
  }

  revision 2014-10-27 {
    description
      "Initial revision. This YANG file defines
       the Network Service Descriptor (NSD)";
    reference
      "Derived from earlier versions of base YANG files";
  }

  typedef parameter-data-type {
    type enumeration {
      enum string;
      enum integer;
      enum boolean;
    }
  }

  grouping primitive-parameter {
    leaf name {
      description
          "Name of the parameter.";
      type string;
    }

    leaf data-type {
      description
          "Data type associated with the name.";
      type parameter-data-type;
    }

    leaf mandatory {
      description "Is this field mandatory";
      type boolean;
      default false;
    }

    leaf default-value {
      description "The default value for this field";
      type string;
    }

    leaf parameter-pool {
      description "NSD Parameter pool name to use for this paramter";
      type string;
    }
  }

  grouping vnf-configuration {
    container vnf-configuration {
      description
          "Information regarding the VNF configuration 
           is captured here. Note that if the NS contains
           multiple instances of the same VNF, each instance
           of the VNF may have different configuration";

      leaf config-type {
        description
            "Must use this configuration type and fill in only pertaining 
             config-method below";
        type enumeration {
          enum none;
          enum netconf;
          enum rest;
          enum script;
          enum juju;
        }
      }

      choice config-method {
        description
            "Defines the configuration method for the VNF.";
        case netconf {
          description
              "Use NETCONF for configuring the VNF.";
          container netconf {
            leaf target {
              description
                  "Netconf configuration target";
              type enumeration {
                enum running;
                enum candidate;
              }
            }

            leaf protocol {
              description
                  "Protocol to use for netconf (e.g. ssh)";
              type enumeration {
                enum None;
                enum ssh;
              }
            }

            leaf port {
              description
                  "Port for the netconf server.";
              type inet:port-number;
            }
          }
        }

        case rest {
          description
              "Use REST for configuring the VNF.";
          container rest {
            leaf port {
              description
                  "Port for the REST server.";
              type inet:port-number;
            }
          }
        }

        case script {
          description
              "Use custom script for configuring the VNF.
               This script is executed in the context of 
               Orchestrator.";
          container script {
            leaf script-type {
              description
                  "Script type - currently supported : bash, expect";
              type enumeration {
                enum bash;
                enum expect;
              }
            }
          }
        }

        case juju {
          description
            "Configure the VNF through Juju.";
          container juju {
            leaf charm {
              description "Juju charm to use with the VNF.";
              type string;
            }
          }
        }
      }

      container config-access {
        leaf mgmt-ip-address {
          description
              "IP address to be used to configure this VNF,
               optional if it is possible to resolve dynamically.";
          type inet:ip-address;
        }

        leaf username {
          description 
              "username for configuration.";
          type string;
        }

        leaf password {
          description 
              "Password for configuration access authentication.";
          type string;
        }
      }

      container input-params {
        description
            "Miscelaneous input parameters to be considered
             while processing the NSD to apply configuration";

        leaf config-priority {
          description
              "Configuration priority - order of confgiration
               to be applied to each VNF in this NS,
               low number gets precedence over high number";
          type uint64;
        }

        leaf config-delay {
          description 
              "Wait (seconds) before applying the configuration to VNF";
          type uint64;
        }
      }

      list config-primitive {
        rwpb:msg-new ConfigPrimitive;
        description
            "List of configuration primitives supported by the
            configuration agent for this VNF.";
        key "name";

        leaf name {
          description
              "Name of the configuration primitive.";
          type string;
        }

        list parameter {
          description
              "List of parameters to the configuration primitive.";
          key "name";
          uses primitive-parameter;
        }
      }

      list initial-config-primitive {
        rwpb:msg-new InitialConfigPrimitive;
        description
            "Initial set of configuration primitives.";
        key "seq";
        leaf seq {
          description
              "Sequence number for the configuration primitive.";
          type uint64;
        }

        leaf name {
          description 
              "Name of the configuration primitive.";
          type string;
        }

        list parameter {
          key "name";
          leaf name {
            type string;
          }

          leaf value {
            type string;
          }
        }
      }

      leaf config-template {
        description
            "Configuration template for each VNF";
        type string;
      }
    }
  } // END - grouping vnf-configuration


  container nsd-catalog {

    list nsd {
      key "id";

      leaf id {
        description "Identifier for the NSD.";
        type yang:uuid;
      }

      leaf name {
        description "NSD name.";
        mandatory true;
        type string;
      }

      leaf short-name {
        description "NSD short name.";
        type string;
      }


      leaf vendor {
        description "Vendor of the NSD.";
        type string;
      }
      
      leaf logo {
        description
          "Vendor logo for the Network Service";
        type string;
      }
      
      leaf description {
        description "Description of the NSD.";
        type string;
      }

      leaf version {
        description "Version of the NSD";
        type string;
      }

      list connection-point {
        description
            "List for external connection points.
            Each NS has one or more external connection
            points. As the name implies that external
            connection points are used for connecting
            the NS to other NS or to external networks.
            Each NS exposes these connection points to
            the orchestrator. The orchestrator can
            construct network service chains by
            connecting the connection points between
            different NS.";

        key "name";
        leaf name {
          description
              "Name of the NS connection point.";
          type string;
        }

        leaf type {
          description
              "Type of the connection point.";
          type manotypes:connection-point-type;
        }
      }

      leaf-list vld-ref {
        type leafref {
          path "/vld:vld-catalog/vld:vld/vld:id";
        }
      }

      /* Still having issues modelling this,
         see the comments under vnfd-connection-point-ref
       */
      list vld {
        description
            "List of Virtual Link Descriptors.";

        key "id";

        leaf id {
          description 
              "Identifier for the VLD.";
          type yang:uuid;
        }

        leaf name {
          description 
              "Virtual Link Descriptor (VLD) name.";
          type string;
        }

        leaf short-name {
          description 
              "Short name for VLD for UI";
          type string;
        }

        leaf vendor {
          description "Provider of the VLD.";
          type string;
        }

        leaf description {
          description "Description of the VLD.";
          type string;
        }

        leaf version {
          description "Version of the VLD";
          type string;
        }

        leaf type {
          type manotypes:virtual-link-type;
        }

        leaf root-bandwidth {
          description
              "For ELAN this is the aggregate bandwidth.";
          type uint64;
        }

        leaf leaf-bandwidth {
          description
              "For ELAN this is the bandwidth of branches.";
          type uint64;
        }

        list vnfd-connection-point-ref {
          description
              "A list of references to connection points.";
          key "member-vnf-index-ref";

          leaf member-vnf-index-ref {
            description "Reference to member-vnf within constituent-vnfds";
            type leafref {
              path "../../../nsd:constituent-vnfd/nsd:member-vnf-index";
            }
          }

           leaf vnfd-id-ref {
             description 
                 "A reference to a vnfd. This is a 
                  leafref to path:
                      ../../../nsd:constituent-vnfd
                      + [nsd:id = current()/../nsd:id-ref]
                      + /nsd:vnfd-id-ref
                  NOTE: An issue with confd is preventing the
                  use of xpath. Seems to be an issue with leafref
                  to leafref, whose target is in a different module.
                  Once that is resovled this will switched to use
                  leafref";
             type yang:uuid;
           }

           leaf vnfd-connection-point-ref {
             description 
                 "A reference to a connection point name 
                  in a vnfd. This is a leafref to path:
                      /vnfd:vnfd-catalog/vnfd:vnfd
                      + [vnfd:id = current()/../nsd:vnfd-id-ref]
                      + /vnfd:connection-point/vnfd:name
                  NOTE: An issue with confd is preventing the
                  use of xpath. Seems to be an issue with leafref
                  to leafref, whose target is in a different module.
                  Once that is resovled this will switched to use
                  leafref";
              type string;
          }
        }

        // replicate for pnfd container here
        uses manotypes:provider-network;
      }

      list constituent-vnfd {
        description
            "List of VNFDs that are part of this
            network service.";

        key "member-vnf-index";

        leaf member-vnf-index {
          description
            "Identifier/index for the VNFD. This separate id
             is required to ensure that multiple VNFs can be
             part of single NS";
          type uint64;
        }

        leaf vnfd-id-ref {
          description
            "Identifier for the VNFD.";
          type leafref {
            path "/vnfd:vnfd-catalog/vnfd:vnfd/vnfd:id";
          }
        }

        // Provide this VNF configuration parameters
        uses vnf-configuration;
      }

      list vnf-dependency {
        description
            "List of VNF dependencies.";
        key vnf-source-ref;
        leaf vnf-source-ref {
          type leafref {
            path "/vnfd:vnfd-catalog/vnfd:vnfd/vnfd:id";
          }
        }
        leaf vnf-depends-on-ref {
          description
              "Reference to VNF that sorce VNF depends.";
          type leafref {
            path "/vnfd:vnfd-catalog/vnfd:vnfd/vnfd:id";
          }
        }
      }

      list vnffgd {
        description
            "List of VNF Forwarding Graph Descriptors (VNFFGD).";

        key "id";

        leaf id {
          description 
              "Identifier for the VNFFGD.";
          type yang:uuid;
        }

        leaf name {
          description 
              "VNFFGD name.";
          type string;
        }

        leaf short-name {
          description 
              "Short name for VNFFGD for UI";
          type string;
        }

        leaf vendor {
          description "Provider of the VNFFGD.";
          type string;
        }

        leaf description {
          description "Description of the VNFFGD.";
          type string;
        }

        leaf version {
          description "Version of the VNFFGD";
          type string;
        }

        list rsp {
          description
              "List of Rendered Service Paths (RSP).";

          key "id";

          leaf id {
            description
                "Identifier for the RSP.";
            type yang:uuid;
          }

          leaf name {
            description
                "RSP name.";
            type string;
          }

          list vnfd-connection-point-ref {
            description
                  "A list of references to connection points.";
            key "member-vnf-index-ref";

            leaf member-vnf-index-ref {
              description "Reference to member-vnf within constituent-vnfds";
              type leafref {
                path "../../../../nsd:constituent-vnfd/nsd:member-vnf-index";
              }
            }

            leaf order {
              type uint8;
              description
                  "A number that denotes the order of a VNF in a chain";
            }

             leaf vnfd-id-ref {
               description 
                   "A reference to a vnfd. This is a 
                    leafref to path:
                        ../../../../nsd:constituent-vnfd
                        + [nsd:id = current()/../nsd:id-ref]
                        + /nsd:vnfd-id-ref
                    NOTE: An issue with confd is preventing the
                    use of xpath. Seems to be an issue with leafref
                    to leafref, whose target is in a different module.
                    Once that is resovled this will switched to use
                    leafref";
               type yang:uuid;
             }

             leaf vnfd-connection-point-ref {
               description 
                   "A reference to a connection point name 
                    in a vnfd. This is a leafref to path:
                        /vnfd:vnfd-catalog/vnfd:vnfd
                        + [vnfd:id = current()/../nsd:vnfd-id-ref]
                        + /vnfd:connection-point/vnfd:name
                    NOTE: An issue with confd is preventing the
                    use of xpath. Seems to be an issue with leafref
                    to leafref, whose target is in a different module.
                    Once that is resovled this will switched to use
                    leafref";
                type string;
            }
          }
        } //rsp

        list classifier {
          description
              "List of classifier rules.";

          key "id";

          leaf id {
            description
                "Identifier for the classifier rule.";
            type yang:uuid;
          }

          leaf name {
            description
                "Name of the classifier.";
            type string;
          }

          leaf rsp-id-ref {
            description
                "A reference to the RSP.";
            type leafref {
              path "../../nsd:rsp/nsd:id";
            }
          }

          
          leaf member-vnf-index-ref {
            description "Reference to member-vnf within constituent-vnfds";
            type leafref {
              path "../../../nsd:constituent-vnfd/nsd:member-vnf-index";
            }
          }

          leaf vnfd-id-ref {
            description 
                "A reference to a vnfd. This is a 
                    leafref to path:
                        ../../../nsd:constituent-vnfd
                        + [nsd:id = current()/../nsd:id-ref]
                        + /nsd:vnfd-id-ref
                    NOTE: An issue with confd is preventing the
                    use of xpath. Seems to be an issue with leafref
                    to leafref, whose target is in a different module.
                    Once that is resovled this will switched to use
                    leafref";
            type yang:uuid;
          }

          leaf vnfd-connection-point-ref {
            description 
                "A reference to a connection point name 
                    in a vnfd. This is a leafref to path:
                        /vnfd:vnfd-catalog/vnfd:vnfd
                        + [vnfd:id = current()/../nsd:vnfd-id-ref]
                        + /vnfd:connection-point/vnfd:name
                    NOTE: An issue with confd is preventing the
                    use of xpath. Seems to be an issue with leafref
                    to leafref, whose target is in a different module.
                    Once that is resovled this will switched to use
                    leafref";
            type string;
          }
             
          list match-attributes {
            description
                "List of match attributes.";

            key "id";

            leaf id {
              description
                  "Identifier for the classifier match attribute rule.";
              type yang:uuid;
            }

            leaf ip-proto {
              description
                  "IP Protocol.";
              type uint8;
            }

            leaf source-ip-address {
              description
                  "Source IP address.";
              type inet:ip-address;
            }

            leaf destination-ip-address {
              description
                  "Destination IP address.";
              type inet:ip-address;
            }

            leaf source-port {
              description
                  "Source port number.";
              type inet:port-number;
            }

            leaf destination-port {
              description
                  "Destination port number.";
              type inet:port-number;
            }
            //TODO: Add more match criteria
          } //match-attributes
        } // classifier
      } // vnffgd

      uses manotypes:monitoring-param;
      uses manotypes:input-parameter-xpath;

      list parameter-pool {
        description
          "Pool of parameter values which must be 
           pulled from during configuration";
        key "name";

        leaf name {
          description
              "Name of the configuration value pool";
          type string;
        }

        container range {
          description
              "Create a range of values to populate the pool with";

          leaf start-value {
            description
                "Generated pool values start at this value";
            type uint32;
            mandatory true;
          }

          leaf end-value {
            description
                "Generated pool values stop at this value";
            type uint32;
            mandatory true;
          }
        }
      }

      list config-primitive {
        description
            "Network service level configuration primitives.";

        key "name";
        leaf name {
          description
              "Name of the configuration primitive.";
          type string;
        }

        list parameter {
          description
              "List of parameters to the configuration primitive.";

          key "name";
          uses primitive-parameter;
        }

        list parameter-group {
          description
              "Grouping of parameters which are logically grouped in UI";
          key "name";

          leaf name {
            description
                "Name of the parameter group";
            type string;
          }

          list parameter {
            description
                "List of parameters to the configuration primitive.";
            key "name";
            uses primitive-parameter;
          }

          leaf mandatory {
            description "Is this parameter group mandatory";
            type boolean;
            default true;
          }
        }

        list vnf-primitive-group {
          description
              "List of configuration primitives grouped by VNF.";

          key "member-vnf-index-ref";
          leaf member-vnf-index-ref {
            description
                "Reference to member-vnf within constituent-vnfds";
            type uint64;
          }

          leaf vnfd-id-ref {
            description
                "A reference to a vnfd. This is a 
                 leafref to path:
                     ../../../../nsd:constituent-vnfd
                     + [nsd:id = current()/../nsd:id-ref]
                     + /nsd:vnfd-id-ref
                 NOTE: An issue with confd is preventing the
                 use of xpath. Seems to be an issue with leafref
                 to leafref, whose target is in a different module.
                 Once that is resovled this will switched to use
                 leafref";

            type string;
          }

          leaf vnfd-name {
            description
                "Name of the VNFD";
            type string;
          }

          list primitive {
            key "index";

            leaf index {
              description "Index of this primitive";
              type uint32;
            }

            leaf name {
              description "Name of the primitive in the VNF primitive ";
              type string;
            }
          }
        }

        leaf user-defined-script {
          description
              "A user defined script.";
          type string;
        }
      }
    }
  }
}
