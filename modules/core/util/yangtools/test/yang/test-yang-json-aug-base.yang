/*
 * 
 * (c) Copyright RIFT.io, 2013-2016, All Rights Reserved
 *
 */



/**
 * @file test-yang-json-aug-base.yang
 * @brief Base yang for testing Json output for augments
 */

module test-yang-json-aug-base {
  namespace "http://riftio.com/ns/riftware-1.0/test-yang-json-aug-base.yang";
  prefix "tyjab";

  description
        "Base yang for testing Json output for augments.";

  revision 2016-02-15 {
        description "Initial version"; 
  }

  container base-cont {
    list person {
      key "name";

      leaf name {
        description
          "Name of the person";
        type string;
      }
      
      leaf phone-no {
        description
          "Phone number of the person";
        type string;
      }
    }
  }
}
