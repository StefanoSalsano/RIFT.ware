/*
 * 
 * (c) Copyright RIFT.io, 2013-2016, All Rights Reserved
 *
 */


/**
 * @file test-yang-json.yang
 * @brief Test YangNode to Json conversion
 */

module test-yang-json
{
  namespace "http://riftio.com/ns/riftware-1.0/test-yang-json.yang";
  prefix "tyj";

  import ietf-inet-types {
    prefix "inet";
  }

  typedef union1 {
     type union {
       type string;
       type enumeration {
          enum RWCAT_E_A { value 1; }
          enum RWCAT_E_B { value 2; }
       }
     }
  }

  container top {
    description "Top Container";

    container choice-cont {
      description "An example with choice statement";

      choice action {
        case annex {
          container annex {
            leaf component-name {
              description "Name of the component type in the inventory";
              type string;
            }
            leaf instance-id {
              description "ID of the component instance in the inventory";
              type string;
            }
            leaf instance-name {
              description "Name of the component instance in the inventory";
              type string;
            }
          }
        }

        case start {
          container start {
            leaf component-name {
              description "Name of the component type in the inventory";
              type string;
            }
            leaf instance-id {
              description "ID of the component instance in the inventory";
              type string;
            }
            leaf instance-name {
              description "Name of the component instance in the inventory";
              type string;
            }
          }
        }

        case sleep {
          container sleep {
            leaf wait-time-usec {
              description "Time to wait while sleeping";
              type uint32;
            }
          }
        }
      } // choice action
    }

  }
}
