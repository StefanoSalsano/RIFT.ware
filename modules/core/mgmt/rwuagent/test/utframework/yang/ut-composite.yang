/*
 * 
 * (c) Copyright RIFT.io, 2013-2016, All Rights Reserved
 *
 *
 */

module ut-composite
{
  namespace "http://riftio.com/ns/core/mgmt/rwuagent/test/ut-composite";
  prefix "utcomposite";

  import ut-types {
    prefix "types";
  }

  import interfaces {
    prefix "interfaces";
  }

  import routes {
    prefix "routes";
  }

  import dns {
    prefix "dns";
  }

  import notif {
    prefix "notif";
  }

  import vehicle-b {
    prefix "example";
  }

  import rw-agent-testbed {
    prefix "rw-agent-testbed";
  }

  import rw-mgmtagt {
    prefix "rw-mgmtagt";
  }
}
