/*
 * 
 * (c) Copyright RIFT.io, 2013-2016, All Rights Reserved
 *
 *
 */

module ietf-resfconf-monitoring-annotation
{
  namespace
      "http://riftio.com/ns/riftware-1.0/ietf-restconf-monitoring-annotation";
  prefix "rcmon-ann";

  import tailf-common {
    prefix tailf;
  }

  import ietf-restconf-monitoring {
    prefix rcmon;
  }

  tailf:annotate "/rcmon:restconf-state" {
    tailf:callpoint base_show;
  }
}
